(defun fun (fname maxnum minnum step)
 (setq num maxnum)
 (while (>= num minnum)
  (setq filename (strcat fname (itoa num) ".dat"))
  (draw filename)
  (setq num (- num step))
 )
)                 

(defun fun2 (fname maxnum minnum step)
 (setq num maxnum)
 (while (>= num minnum)
  (setq filename (strcat fname (itoa num) ".dat"))
  (draw3 filename)
  (setq num (- num step))
 )
)                 

(defun funp2 (fname maxnum minnum step)
 (setq num maxnum)
 (while (>= num minnum)
  (setq filename (strcat fname (itoa num) ".dat"))
  (drawp2 filename)
  (setq num (- num step))
 )
)                 

(defun funp (fname maxnum minnum step)
 (setq num maxnum)
 (while (>= num minnum)
  (setq filename (strcat fname (itoa num) ".dat"))
  (drawp filename)
  (setq num (- num step))
 )
)                 


(defun draw (filename)
 (setq path (findfile filename))
 (if (not (= path nil))
   (progn 
   (setq f (open path "r"))
   (setq i 1)
   (while (not (null (setq line (read-line f))))
     (if (= i 1)
     (progn
       (setq p2 (read line))
     )
     (progn
       (setq p1 p2 
             p2 (read line))
       (command "ОТРЕЗОК" p1 p2 "")
     )
     )
     (setq i (+ i 1))
   )
   (close f)
   )
   (princ "file Not found")
   )
)

(defun draw2 (filename)
 (setq path (findfile filename))
 (if (not (= path nil))
   (progn 
   (setq f (open path "r"))
   (while (not (null (setq line (read-line f))))
       (setq p1 (read line) 
             p2 (read (read-line f)))
       (command "ОТРЕЗОК" p1 p2 "")
   )
   (close f)
   )
   (princ "file Not found")
   )
)

(defun drawc (filename)
 (setq path (findfile filename))
 (if (not (= path nil))
   (progn 
   (setq f (open path "r"))
   (while (not (null (setq line (read-line f))))
       (setq p1 (read line))
       (command "КРУГ" p1 "1.0")
   )
   (close f)
   )
   (princ "file Not found")
   )
)



(defun draw3 (filename)
 (setq path (findfile filename))
 (if (not (= path nil))
   (progn 
   (setq f (open path "r"))
   (read-line f)
   (setq i 1)
   (while (not (null (setq line (read-line f))))
     (if (= i 1)
     (progn
       (setq p2 (read line))
     )
     (progn
       (setq p1 p2 
             p2 (read line))
       (command "ОТРЕЗОК" p1 p2 "")
     )
     )
     (setq i (+ i 1))
   )
   (close f)
   )
   (princ "file Not found")
   )
)

(defun drawp (filename)
 (setq path (findfile filename))
 (if (not (= path nil))
   (progn 
   (setq f (open path "r"))
   (setq i 1)
   (while (not (null (setq line (read-line f))))
     (if (= i 1)
     (progn
       (setq p2 (read line))
       (command "3dПЛИНИЯ" p2)
     )
     (progn
       (setq p2 (read line))
       (command p2)
     )
     )
     (setq i (+ i 1))
   )
   (command "")
   (close f)
   )
   (princ "file Not found")
   )
)


(defun drawp2 (filename)
 (setq path (findfile filename))
 (if (not (= path nil))
   (progn 
   (setq f (open path "r"))
   (read-line f)
   (setq i 1)
   (while (not (null (setq line (read-line f))))
     (if (= i 1)
     (progn
       (setq p2 (read line))
       (command "3dПЛИНИЯ" p2)
     )
     (progn
       (setq p2 (read line))
       (command p2)
     )
     )
     (setq i (+ i 1))
   )
   (command "")
   (close f)
   )
   (princ "file Not found")
   )
)


(defun funmesh (fname1 fname2 maxnum minnum step)
 (setq num maxnum)
 (while (>= num minnum)
  (setq filename1 (strcat fname1 (itoa num) ".dat"))
  (setq filename2 (strcat fname2 (itoa num) ".dat"))
  (drawmesh filename1 filename2)
  (setq num (- num step))
 )
)                 

(defun drawmesh (filename1 filename2)
 (setq path1 (findfile filename1)
       path2 (findfile filename2))
 (if (not (or (= path1 nil) (= path2 nil)))
   (progn 
   (setq f1 (open path1 "r")
         f2 (open path2 "r"))
   (setq i 1)
   (while (not (null (setq line (read-line f1))))
     (if (= i 1)
     (progn
       (setq p2 (read line))
       (command "3dmesh" "2" "101" p2)
     )
     (progn
       (setq p2 (read line))
       (command p2)
     )
     )
     (setq i (+ i 1))
   )
   (close f1)
   (setq i 1)
   (while (not (null (setq line (read-line f2))))
   (progn
     (setq p2 (read line))
     (command p2)
   )
   )
   (close f2)
   )
   (princ "file Not found")
   )
 
)
